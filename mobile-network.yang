module mobile-network{
    container subscribers{
        description 
            "Saves multiple subscribers";
        list subscriber{
            key number;
            leaf number{
                type string{
                    pattern "\\+?[0-9]+(-[0-9]+)*";
                }
                mandatory "true";
                description
                    "Subscriber's phone number";
            }
            leaf userName{
                type string;
                mandatory "true";
                description
                    "Subscriber's name";
            }
            leaf incomingNumber{
                type string{
                    pattern "\\+?[0-9]+(-[0-9]+)*";
                }
                description
                    "Incoming phone number";
            }
            leaf state{
                type enumeration{
                    enum busy{
                        description
                            "Subscriber is busy";
                    }
                    enum hangUp{
                        description 
                            "Subscriber is hanging up";
                    }
                }
                mandatory "true";
                description
                    "States of subscriber";
            }
        }
    }
}
